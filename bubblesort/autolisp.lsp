(defun bubble-sort (lst / arr n i tmp swapped)
  (setq arr (apply 'vector lst))
  (setq n (length lst))
  (setq swapped T)
  (while swapped
    (setq swapped nil)
    (setq i 0)
    (while (< i (1- n))
      (if (> (svref arr i) (svref arr (1+ i)))
        (progn
          (setq tmp (svref arr i))
          (svset arr i (svref arr (1+ i)))
          (svset arr (1+ i) tmp)
          (setq swapped T)
        )
      )
      (setq i (1+ i))
    )
    (setq n (1- n))
  )
  (setq i 0)
  (setq lst nil)
  (while (< i (vl-vector-length arr))
    (setq lst (append lst (list (svref arr i))))
    (setq i (1+ i))
  )
  lst
)

(print (bubble-sort '(64 34 25 12 22 11 90)))
